FME workspace FME Query and Upload Example.fmw
Title: Datagovau Write to CKAN
Description: Workbench writes directly to www.data.gov.au using the CKAN API
History: 2015-06-01,Matt Swards,City of Ballarat

Parameters:
- Authorisation =
- Dataset_ID =
- FME_USER_PARAM_PRIVATE_GRP =

Note: Matt Swards / City of Ballarat / matthewswards@ballarat.vic.gov.au / 03 5320 5600 / v1
Note: 1. MAKE A PRIVATE PARAMETER WITH YOUR AUTHORISATION/API KEY. THIS CAN BE FOUND ON YOUR PROFILE FROM DATA.GOV.AU. THIS WILL BE USED AS A HEADER IN THE FINAL HTTPCALLER
Creator
    GEOMTYPE = Geometry Object
    NUM = 1
    CREATED -> AttributeCreator
AttributeCreator
    ATTR_TABLE = SET_TO queryURL = https://data.gov.au/api/3/action/package_show?id=$(Dataset_ID)
    -> HTTPCaller
Note: Call the dataset you wish to update via request URL and / rename response body attribute to response / https://data.gov.au/api/3/action/package_show?id=DATASET_ID
HTTPCaller
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = response
    TARGET_ATTR_ENCODING = auto-detect
    TARGET_URL = @Value(queryURL)
    TRANSFER_TIMEOUT_LENGTH = 90
    USE_COOKIES = No
    VERIFY_SSL_CERTIFICATES = Yes
    -> JSONFlattener
Note: Flatten the response
JSONFlattener
    JSON_ATTR = response
    RECURSIVE = Yes
    -> AttributeExposer
Note: Expose attributes from the response including id, / format and response list eg: response{}
AttributeExposer
    ATTR_LIST = result.resources{},format,result.id
    -> AttributeRenamer
Note: Rename the id to groupid. We need to extract / each resource id and this will cause havoc otherwise
AttributeRenamer
    ATTR_LIST = result.id,groupid,id
    -> AttributeRemover
AttributeRemover
    LIST_ATTRS = _headers{} _headers{}.name _headers{}.value
    -> ListExploder_2
Note: Explode the resource list to / extract each resource
ListExploder_2
    ATTR_ACCUM_MODE = Merge Incoming List
    ATTR_CONFLICT_RES = Use Original
    INDEX_ATTR = _element_index
    LIST_ATTR = result.resources{}
    LIST_FOUND -> AttributeExposer_2
Note: any attributes you would like to update on the resource such as last-modified, description etc can be exposed here for editing then pushed to an attribute setter if needed
AttributeExposer_2
    ATTR_LIST = id,package_id,url,ckan_url
    -> AttributeFilter
Note: Filter out by each resource format. This will / allow us to update each particular resource / with the right dataset. A logger after the JSON Flattener / will give you the different formats of each dataset
AttributeFilter
    ATTR_NAME = format
    ATTR_VALUES = <EMPTY>,<MISSING>,<NULL>,<UNFILTERED>,CSV,shp,KML
    CSV -> TimeStamper_2
    KML -> TimeStamper
Note: TimeStamper for the last_modified date of the resource
TimeStamper_2
    FMT = ISO Date (^Y-^m-^d)
    TIME_ATTR = last_modified
    -> HTTPCaller_2__2
Note: URL / http://data.gov.au/api/3/action/resource_update / Method - POST / HEADERS / Authorization - your private parameter API KEY / BODY / Multipart/form data / UPLOAD / Required fields / id - the id of the resource which has been extracted earlier / upload - the file being upload. needs application/octet-stream as mime type / Optional / last_modified - the last modified date created with the time stamper / any other field you might wish to update such as description etc
HTTPCaller_2__2
    CONNECTION_TIMEOUT_LENGTH = 60
    CUSTOM_HEADERS = Authorization;$(Authorisation)
    ERROR_ATTR = _error
    FOLLOW_REDIRECTS = No
    HTTP_METHOD = POST
    MULTIPARTS = id StringUpload SOURCE_EXPRESSION;@Value(id);MIME_TYPE;text/plain;FME_CONTROLLER_QUERY_FILE;transformers\dependencies\http\StringUpload.fme upload FileUpload SOURCE_FILE;C:\Temp\Hello there.txt;MIME_TYPE;application/octet-stream;FME_CONTROLLER_QUERY_FILE;transformers\dependencies\http\FileUpload.fme last_modified StringUpload SOURCE_EXPRESSION;@Value(last_modified);MIME_TYPE;text/plain;FME_CONTROLLER_QUERY_FILE;transformers\dependencies\http\StringUpload.fme
    RESPONSE_HEADER_LIST_ATTR = _headers
    SAVE_FILE = Attribute
    STATUS_CODE_ATTR = _http_status_code
    TARGET_ATTR = _response_body
    TARGET_ATTR_ENCODING = auto-detect
    TARGET_URL = http://data.gov.au/api/3/action/resource_update
    TRANSFER_TIMEOUT_LENGTH = 90
    UPLOAD_TYPE = Multipart / Form Data
    USE_COOKIES = No
    VERIFY_SSL_CERTIFICATES = Yes
    -> HTTPCaller_2__2_Output
    <REJECTED> -> HTTPCaller_2__2_Output
HTTPCaller_2__2_Output: Logger
    MAXCOORDS = 20
    MAXFEATS = 20
    MESSAGE = Feature is:
TimeStamper
    FMT = ISO Date (^Y-^m-^d)
    TIME_ATTR = last_modified
    -> HTTPCaller_2_
HTTPCaller_2_
    CONNECTION_TIMEOUT_LENGTH = 60
    CUSTOM_HEADERS = Authorization;$(Authorisation)
    ERROR_ATTR = _error
    FOLLOW_REDIRECTS = Yes
    HTTP_METHOD = POST
    MULTIPARTS = id StringUpload SOURCE_EXPRESSION;@Value(id);MIME_TYPE;text/plain;FME_CONTROLLER_QUERY_FILE;transformers\dependencies\http\StringUpload.fme upload FileUpload SOURCE_FILE;C:\Temp\Hello there.txt;MIME_TYPE;application/octet-stream;FME_CONTROLLER_QUERY_FILE;transformers\dependencies\http\FileUpload.fme last_modified StringUpload SOURCE_EXPRESSION;@Value(last_modified);MIME_TYPE;text/plain;FME_CONTROLLER_QUERY_FILE;transformers\dependencies\http\StringUpload.fme
    RESPONSE_HEADER_LIST_ATTR = _headers
    SAVE_FILE = Attribute
    STATUS_CODE_ATTR = _http_status_code
    TARGET_ATTR = _response_body
    TARGET_ATTR_ENCODING = auto-detect
    TARGET_URL = https://data.gov.au/api/3/action/resource_update
    TRANSFER_TIMEOUT_LENGTH = 90
    UPLOAD_TYPE = Multipart / Form Data
    USE_COOKIES = No
    VERIFY_SSL_CERTIFICATES = Yes
    -> HTTPCaller_2__Output
    <REJECTED> -> HTTPCaller_2__Output
HTTPCaller_2__Output: Logger
    MAXCOORDS = 20
    MAXFEATS = 20
    MESSAGE = Feature is:
