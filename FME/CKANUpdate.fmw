FME workspace CKANUpdate.fmw
Title: Datagovau Write to CKAN
Description: Workbench writes directly to www.data.gov.au using the CKAN API
History: 2015-06-01,Matt Swards,City of Ballarat

Parameters:
- Authorisation = APIKEYHERE   # API Key

Note: Matt Swards / City of Ballarat / matthewswards@ballarat.vic.gov.au / 03 5320 5600 / v1
Note: 1. MAKE A PRIVATE PARAMETER WITH YOUR AUTHORISATION/API KEY. THIS CAN BE FOUND ON YOUR PROFILE FROM DATA.GOV.AU. THIS WILL BE USED AS A HEADER IN THE FINAL HTTPCALLER
Creator
    NUM = 1
    GEOMTYPE = Geometry Object
    CREATED -> HTTPCaller
Note: Call the dataset you wish to update via request URL and / rename response body attribute to response / https://data.gov.au/api/rest/dataset/DATASET_URL
HTTPCaller
    USE_COOKIES = No
    CONNECTION_TIMEOUT_LENGTH = 60
    FOLLOW_REDIRECTS = Yes
    RESPONSE_HEADER_LIST_ATTR = _headers
    VERIFY_SSL_CERTIFICATES = Yes
    STATUS_CODE_ATTR = _http_status_code
    TARGET_ATTR = response
    HTTP_METHOD = GET
    TARGET_ATTR_ENCODING = auto-detect
    SAVE_FILE = Attribute
    ERROR_ATTR = _error
    TRANSFER_TIMEOUT_LENGTH = 90
    TARGET_URL = https://data.gov.au/api/rest/dataset/DATASET_URL
    -> JSONFlattener
Note: Flatten the response
JSONFlattener
    RECURSIVE = Yes
    JSON_ATTR = response
    -> AttributeExposer
Note: Expose attributes from the response including id, / format and response list eg: response{}
AttributeExposer
    ATTR_LIST = resources{},format,id
    -> AttributeRenamer
Note: Rename the id to groupid. We need to extract / each resource id and this will cause havoc otherwise
AttributeRenamer
    ATTR_LIST = id,groupid,id
    -> AttributeRemover
AttributeRemover
    LIST_ATTRS = _headers{} _headers{}.name _headers{}.value
    -> ListExploder_2
Note: Explode the resource list to / extract each resource
ListExploder_2
    LIST_ATTR = resources{}
    ATTR_CONFLICT_RES = Use Original
    ATTR_ACCUM_MODE = Merge Incoming List
    INDEX_ATTR = _element_index
    LIST_FOUND -> AttributeExposer_2
Note: any attributes you would like to update on the resource such as last-modified, description etc can be exposed here for editing then pushed to an attribute setter if needed
AttributeExposer_2
    ATTR_LIST = id,package_id,url,ckan_url
    -> AttributeFilter
Note: Filter out by each resource format. This will / allow us to update each particular resource / with the right dataset. A logger after the JSON Flattener / will give you the different formats of each dataset
AttributeFilter
    ATTR_VALUES = <EMPTY>,<MISSING>,<NULL>,<UNFILTERED>,CSV,shp,KML
    ATTR_NAME = format
    KML -> TimeStamper
    CSV -> TimeStamper_2
Note: TimeStamper for the last_modified date of the resource
TimeStamper_2
    TIME_ATTR = last_modified
    FMT = ISO Date (^Y-^m-^d)
    -> HTTPCaller_2__2
Note: URL / http://data.gov.au/api/3/action/resource_update / Method - POST / HEADERS / Authorization - your private parameter API KEY / BODY / Multipart/form data / UPLOAD / Required fields / id - the id of the resource which has been extracted earlier / upload - the file being upload. needs application/octet-stream as mime type / Optional / last_modified - the last modified date created with the time stamper / any other field you might wish to update such as description etc
HTTPCaller_2__2
    USE_COOKIES = No
    CONNECTION_TIMEOUT_LENGTH = 60
    MULTIPARTS = id StringUpload SOURCE_EXPRESSION;@Value(id);MIME_TYPE;text/plain;FME_CONTROLLER_QUERY_FILE;transformers\dependencies\http\StringUpload.fme upload FileUpload SOURCE_FILE;C:\Temp\Hello there.txt;MIME_TYPE;application/octet-stream;FME_CONTROLLER_QUERY_FILE;transformers\dependencies\http\FileUpload.fme last_modified StringUpload SOURCE_EXPRESSION;@Value(last_modified);MIME_TYPE;text/plain;FME_CONTROLLER_QUERY_FILE;transformers\dependencies\http\StringUpload.fme
    FOLLOW_REDIRECTS = No
    RESPONSE_HEADER_LIST_ATTR = _headers
    VERIFY_SSL_CERTIFICATES = Yes
    CUSTOM_HEADERS = Authorization;$(Authorisation)
    STATUS_CODE_ATTR = _http_status_code
    TARGET_ATTR = _response_body
    HTTP_METHOD = POST
    UPLOAD_TYPE = Multipart / Form Data
    TARGET_ATTR_ENCODING = auto-detect
    SAVE_FILE = Attribute
    ERROR_ATTR = _error
    TRANSFER_TIMEOUT_LENGTH = 90
    TARGET_URL = http://data.gov.au/api/3/action/resource_update
    -> HTTPCaller_2__2_Output
    <Rejected> -> HTTPCaller_2__2_Output
HTTPCaller_2__2_Output: Logger
    MAXFEATS = 20
    MESSAGE = Feature is:
    MAXCOORDS = 20
TimeStamper
    TIME_ATTR = last_modified
    FMT = ISO Date (^Y-^m-^d)
    -> HTTPCaller_2_
HTTPCaller_2_
    USE_COOKIES = No
    CONNECTION_TIMEOUT_LENGTH = 60
    MULTIPARTS = id StringUpload SOURCE_EXPRESSION;@Value(id);MIME_TYPE;text/plain;FME_CONTROLLER_QUERY_FILE;transformers\dependencies\http\StringUpload.fme upload FileUpload SOURCE_FILE;C:\Temp\Hello there.txt;MIME_TYPE;application/octet-stream;FME_CONTROLLER_QUERY_FILE;transformers\dependencies\http\FileUpload.fme last_modified StringUpload SOURCE_EXPRESSION;@Value(last_modified);MIME_TYPE;text/plain;FME_CONTROLLER_QUERY_FILE;transformers\dependencies\http\StringUpload.fme
    FOLLOW_REDIRECTS = Yes
    RESPONSE_HEADER_LIST_ATTR = _headers
    VERIFY_SSL_CERTIFICATES = Yes
    CUSTOM_HEADERS = Authorization;$(Authorisation)
    STATUS_CODE_ATTR = _http_status_code
    TARGET_ATTR = _response_body
    HTTP_METHOD = POST
    UPLOAD_TYPE = Multipart / Form Data
    TARGET_ATTR_ENCODING = auto-detect
    SAVE_FILE = Attribute
    ERROR_ATTR = _error
    TRANSFER_TIMEOUT_LENGTH = 90
    TARGET_URL = https://data.gov.au/api/3/action/resource_update
    -> HTTPCaller_2__Output
    <Rejected> -> HTTPCaller_2__Output
HTTPCaller_2__Output: Logger
    MAXFEATS = 20
    MESSAGE = Feature is:
    MAXCOORDS = 20
