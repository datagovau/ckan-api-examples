FME workspace FME Upload Example.fmw

Parameters:
- Authorization =
- Private_Group =
- Resource_ID =
- Upload_File =

Note: Before running this workspace please enter your API key under the Private group within User Parameters. / File to upload and the resource id will be prompted upon workspace run.
Creator
    GEOMTYPE = Geometry Object
    NUM = 1
    CREATED -> HTTPCaller
Note: Sends a POST request to the following API URL: https://data.gov.au/data/api/action/resource_update / In this request it has: / HEADER / Authorization: API_KEY / BODY / Multipart/form-data / upload: UPLOAD_FILE / id: RESOURCE_ID / If you want to pass extra metadata values you can add additional attributes to the body of this HTTPCaller
HTTPCaller
    CONNECTION_TIMEOUT_LENGTH = 60
    CUSTOM_HEADERS = Authorization;$(Authorization)
    ERROR_ATTR = _error
    FOLLOW_REDIRECTS = DO_NOT_FOLLOW
    HTTP_METHOD = POST
    MAX_HTTP_VERSION = HTTP_2
    MAX_TRANSFERS_IN_PROGRESS = 25
    MULTIPARTS = id StringUpload SOURCE_EXPRESSION;$(Resource_ID);MIME_TYPE;text/plain;FME_CONTROLLER_QUERY_FILE;transformers/dependencies/http/StringUpload.fme;FME_CONTROLLER_CHOICE;StringUpload upload FileUpload SOURCE_FILE;$(Upload_File);MIME_TYPE;application/octet-stream;FME_CONTROLLER_QUERY_FILE;transformers/dependencies/http/FileUpload.fme;FME_CONTROLLER_CHOICE;FileUpload
    SAVE_FILE = Attribute
    STATUS_CODE_ATTR = _http_status_code
    TARGET_ATTR = _response_body
    TARGET_ATTR_ENCODING = auto-detect
    TARGET_URL = https://data.gov.au/data/api/action/resource_update
    TRANSFER_TIMEOUT_LENGTH = 90
    UPLOAD_TYPE = Multipart / Form Data
    USE_COOKIES = No
    VERIFY_SSL_CERTIFICATES = Yes
    -> Logger
    <REJECTED> -> Logger
Logger
    LOG_FEATURE = LOG_RECORD
    MAXCOORDS = 20
    MAXFEATS = 20
    MESSAGE = Feature is:
    SEVERITY = INFO
